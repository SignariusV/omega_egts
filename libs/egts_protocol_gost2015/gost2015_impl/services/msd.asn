-- ASN.1 спецификация MSD (Минимальный набор данных)
-- ГОСТ 33464-2015, Приложение А
-- Кодирование: Unaligned PER (codec='per' в asn1tools)

MSDASN1Module DEFINITIONS AUTOMATIC TAGS ::=
BEGIN

-- Главное сообщение MSD
MSDMessage ::= SEQUENCE {
    msdStructure            MSDStructure,
    optionalAdditionalData  ERAAdditionalData OPTIONAL
}

-- Структура МСД
MSDStructure ::= SEQUENCE {
    messageIdentifier           INTEGER (0..255),
    control                     ControlType,
    vehicleIdentificationNumber VehicleIdentificationNumber,
    vehiclePropulsionStorageType VehiclePropulsionStorageType,
    timestamp                   INTEGER (0..4294967295),
    vehicleLocation             VehicleLocation,
    vehicleDirection            INTEGER (0..511),
    numberOfPassengers          INTEGER (0..255) OPTIONAL
}

-- Тип управления вызовом
ControlType ::= SEQUENCE {
    automaticActivation    BOOLEAN,
    testCall               BOOLEAN,
    positionCanBeTrusted   BOOLEAN,
    vehicleType            INTEGER (1..13)
}

-- VIN код (ISO 3779)
VehicleIdentificationNumber ::= SEQUENCE {
    isowmi              IA5String (SIZE(3)),
    isovds              IA5String (SIZE(6)),
    isovisModelyear     IA5String (SIZE(1)),
    isovisSeqPlant      IA5String (SIZE(7))
}

-- Тип топливной системы
VehiclePropulsionStorageType ::= SEQUENCE {
    gasolineTankPresent       BOOLEAN,
    dieselTankPresent         BOOLEAN,
    compressedNaturalGas      BOOLEAN,
    liquidPropaneGas          BOOLEAN,
    electricEnergyStorage     BOOLEAN,
    hydrogenStorage           BOOLEAN
}

-- Координаты (микросекунды дуги)
VehicleLocation ::= SEQUENCE {
    positionLatitude    INTEGER (-2147483648..2147483647),
    positionLongitude   INTEGER (-2147483648..2147483647)
}

-- Дополнительные данные ЭРА-ГЛОНАСС
ERAAdditionalData ::= SEQUENCE {
    oid     OBJECT IDENTIFIER,
    data    OCTET STRING
}

END
